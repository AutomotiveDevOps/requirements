[DOCUMENT]
TITLE: MIL-STD-498 IRS (Interface Requirements Specification)

[REQUIREMENT]
UID: IRS-1
STATUS: Draft
TITLE: MIL-STD-498 IRS (Interface Requirements Specification)
STATEMENT: This requirement covers MIL-STD-498 IRS (Interface Requirements Specification).
RATIONALE: Converted from original document structure.

[REQUIREMENT]
UID: IRS-2
STATUS: Draft
TITLE: Logging Interface
STATEMENT: This requirement covers Logging Interface.
RATIONALE: Converted from original document structure.
