[DOCUMENT]
TITLE: MIL-STD-498 SSDD (Software System Design Description)

[REQUIREMENT]
UID: SSDD-1
STATUS: Draft
TITLE: MIL-STD-498 SSDD (Software System Design Description)
STATEMENT: This requirement covers MIL-STD-498 SSDD (Software System Design Description).
RATIONALE: Converted from original document structure.

[REQUIREMENT]
UID: SSDD-2
STATUS: Draft
TITLE: Data Design
STATEMENT: This requirement covers Data Design.
RATIONALE: Converted from original document structure.
