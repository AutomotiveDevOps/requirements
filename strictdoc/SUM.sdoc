[DOCUMENT]
TITLE: MIL-STD-498 SUM (Software User Manual)

[REQUIREMENT]
UID: SUM-1
STATUS: Draft
TITLE: MIL-STD-498 SUM (Software User Manual)
STATEMENT: This requirement covers MIL-STD-498 SUM (Software User Manual).
RATIONALE: Converted from original document structure.

[REQUIREMENT]
UID: SUM-2
STATUS: Draft
TITLE: User Notes
STATEMENT: This requirement covers User Notes.
RATIONALE: Converted from original document structure.
