[DOCUMENT]
TITLE: MIL-STD-498 STD (Software Test Description)

[REQUIREMENT]
UID: STD-1
STATUS: Draft
TITLE: MIL-STD-498 STD (Software Test Description)
STATEMENT: This requirement covers MIL-STD-498 STD (Software Test Description).
RATIONALE: Converted from original document structure.

[REQUIREMENT]
UID: STD-2
STATUS: Draft
TITLE: Test Tools
STATEMENT: This requirement covers Test Tools.
RATIONALE: Converted from original document structure.
