[DOCUMENT]
TITLE: MIL-STD-498 SDD (Software Design Description)

[REQUIREMENT]
UID: SDD-1
STATUS: Draft
TITLE: MIL-STD-498 SDD (Software Design Description)
STATEMENT: This requirement covers MIL-STD-498 SDD (Software Design Description).
RATIONALE: Converted from original document structure.

[REQUIREMENT]
UID: SDD-2
STATUS: Draft
TITLE: Design Notes
STATEMENT: This requirement covers Design Notes.
RATIONALE: Converted from original document structure.
