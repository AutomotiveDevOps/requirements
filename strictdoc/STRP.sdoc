[DOCUMENT]
TITLE: MIL-STD-498 STRP (Software Transition Plan)

[REQUIREMENT]
UID: STRP-1
STATUS: Draft
TITLE: MIL-STD-498 STRP (Software Transition Plan)
STATEMENT: This requirement covers MIL-STD-498 STRP (Software Transition Plan).
RATIONALE: Converted from original document structure.

[REQUIREMENT]
UID: STRP-2
STATUS: Draft
TITLE: Test Summary
STATEMENT: This requirement covers Test Summary.
RATIONALE: Converted from original document structure.
