[DOCUMENT]
TITLE: MIL-STD-498 SRS (Software Requirements Specification)

[REQUIREMENT]
UID: SRS-1
STATUS: Draft
TITLE: MIL-STD-498 SRS (Software Requirements Specification)
STATEMENT: This requirement covers MIL-STD-498 SRS (Software Requirements Specification).
RATIONALE: Converted from original document structure.

[REQUIREMENT]
UID: SRS-2
STATUS: Draft
TITLE: Authentication and Authorization
STATEMENT: This requirement covers Authentication and Authorization.
RATIONALE: Converted from original document structure.
