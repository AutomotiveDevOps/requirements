[DOCUMENT]
TITLE: Advanced StrictDoc Features Example

[REQUIREMENT]
UID: 02_-1
STATUS: Draft
TITLE: Advanced StrictDoc Features Example
STATEMENT: This requirement covers Advanced StrictDoc Features Example.
RATIONALE: Converted from original document structure.

[REQUIREMENT]
UID: 02_-2
STATUS: Draft
TITLE: Accessibility Compliance
STATEMENT: This requirement covers Accessibility Compliance.
RATIONALE: Converted from original document structure.
