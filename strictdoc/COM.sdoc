[DOCUMENT]
TITLE: MIL-STD-498 COM (Computer Operation Manual)

[REQUIREMENT]
UID: COM-1
STATUS: Draft
TITLE: MIL-STD-498 COM (Computer Operation Manual)
STATEMENT: This requirement covers MIL-STD-498 COM (Computer Operation Manual).
RATIONALE: Converted from original document structure.

[REQUIREMENT]
UID: COM-2
STATUS: Draft
TITLE: Performance Monitoring
STATEMENT: This requirement covers Performance Monitoring.
RATIONALE: Converted from original document structure.
