[DOCUMENT]
TITLE: MIL-STD-498 SPS (Software Product Specification)

[REQUIREMENT]
UID: SPS-1
STATUS: Draft
TITLE: MIL-STD-498 SPS (Software Product Specification)
STATEMENT: This requirement covers MIL-STD-498 SPS (Software Product Specification).
RATIONALE: Converted from original document structure.

[REQUIREMENT]
UID: SPS-2
STATUS: Draft
TITLE: Resource Requirements
STATEMENT: This requirement covers Resource Requirements.
RATIONALE: Converted from original document structure.
