[DOCUMENT]
TITLE: Lorem

[SECTION]
TITLE: Introduction

[FREETEXT]
Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.
[/FREETEXT]

[/SECTION]

[SECTION]
TITLE: Examples

[FREETEXT]
"Hello World" example of the text language:

.. code-block:: text

    [DOCUMENT]
    TITLE: StrictDoc

    [REQUIREMENT]
    UID: SDOC-HIGH-REQS-MANAGEMENT
    TITLE: Requirements management
    STATEMENT: StrictDoc shall enable requirements management.
[/FREETEXT]

[FREETEXT]
For a more comprehensive example check the source file of this documentation
which is written using StrictDoc:
`strictdoc.sdoc <https://github.com/strictdoc-project/strictdoc/blob/master/docs/strictdoc.sdoc>`_.

- `StrictDoc HTML export <https://strictdoc.readthedocs.io/en/latest/strictdoc-html>`_
- `StrictDoc HTML export using Sphinx <https://strictdoc.readthedocs.io/en/latest>`_
- `StrictDoc PDF export using Sphinx <https://strictdoc.readthedocs.io/_/downloads/en/latest/pdf/>`_
[/FREETEXT]

[/SECTION]

[SECTION]
TITLE: Getting started

[SECTION]
TITLE: Requirements

[FREETEXT]
- This
- Is
- A
- List
[/FREETEXT]

[/SECTION]

[SECTION]
TITLE: Installing StrictDoc as a Pip package (recommended way)

[FREETEXT]
.. code-block:: text

    pip install strictdoc
[/FREETEXT]

[/SECTION]

[SECTION]
TITLE: Installing StrictDoc from GitHub (developer mode)

[FREETEXT]
**Note:** Use this way of installing StrictDoc only if you want to make changes
in StrictDoc's source code. Otherwise, install StrictDoc as a Pip package
(see above).

StrictDoc uses Poetry, so `Poetry <https://python-poetry.org>`_ has to be
installed. To install Poetry, read the instructions here:
`Poetry / Installation <https://python-poetry.org/docs/#installation>`_.

When Poetry is installed, clone StrictDoc:

.. code-block:: text

    git clone https://github.com/strictdoc-project/strictdoc.git && cd strictdoc
    poetry install
    poetry run strictdoc
    poetry run invoke test

StrictDoc can also be developed and run without Poetry:

.. code-block:: text

    git clone https://github.com/strictdoc-project/strictdoc.git && cd strictdoc
    pip install -r requirements.txt
    python3 strictdoc/cli/main.py
    # for running tests:
    pip install invoke pytest pytidylib html5lib
    invoke test
[/FREETEXT]

[/SECTION]

[SECTION]
TITLE: Hello world

[FREETEXT]
.. code-block:: text

    git clone --depth 1 https://github.com/strictdoc-project/strictdoc && cd strictdoc
    strictdoc export docs/
[/FREETEXT]

[/SECTION]

[/SECTION]

[SECTION]
TITLE: SDoc syntax

[FREETEXT]
StrictDoc defines a special syntax for writing specifications documents. This
syntax is called SDoc and it's grammar is encoded with the
`textX <https://github.com/textX/textX>`_
tool.

The grammar is defined using textX language for defining grammars and is
located in a single file:
`grammar.py <https://github.com/strictdoc-project/strictdoc/blob/master/strictdoc/backend/dsl/grammar.py>`_.

This is how a minimal possible SDoc document looks like:

.. code-block:: text

    [DOCUMENT]
    TITLE: StrictDoc

This documentation is written using StrictDoc. Here is the source file:
`strictdoc.sdoc <https://github.com/strictdoc-project/strictdoc/blob/master/docs/strictdoc.sdoc>`_.
[/FREETEXT]

[SECTION]
TITLE: Document structure

[FREETEXT]
An SDoc document consists of a ``[DOCUMENT]`` declaration followed by one or many
``[REQUIREMENT]`` or ``[COMPOSITE_REQUIREMENT]`` statements which can be grouped
into ``[SECTION]`` blocks.

The following grammatical constructs are currently supported:

- ``DOCUMENT``

  - ``FREE_TEXT``

- ``REQUIREMENT`` and ``COMPOSITE_REQUIREMENT``

- ``SECTION``

  - ``FREE_TEXT``

Each construct is described in more detail below.
[/FREETEXT]

[SECTION]
TITLE: Strict rule #1: One empty line between all nodes

[FREETEXT]
StrictDoc's grammar requires each node, such as ``[REQUIREMENT]``, ``[SECTION]``,
etc., to be separated with exactly one empty line from the nodes surrounding it.
This rule is valid for all nodes. Absence of an empty line or presence of more
than one empty line between two nodes will result in an SDoc parsing error.
[/FREETEXT]

[/SECTION]

[SECTION]
TITLE: Strict rule #2: No content is allowed outside of SDoc grammar

[FREETEXT]
StrictDoc's grammar does not allow any content to be written outside of the SDoc
grammatical constructs. It is assumed that the critical content shall always be
written in form of requirements:
``[REQUIREMENT]`` and ``[COMPOSITE_REQUIREMENT]``. Non-critical content shall
be specified using ``[FREETEXT]`` nodes. By design, the ``[FREETEXT]`` nodes can
be only attached to the ``[DOCUMENT]`` and ``[SECTION]`` nodes.
[/FREETEXT]

[/SECTION]

[/SECTION]

[SECTION]
TITLE: Grammar elements

[SECTION]
TITLE: Document

[FREETEXT]
``[DOCUMENT]`` element must always be present in an SDoc document. It is a root
of an SDoc document graph.

.. code-block:: text

    [DOCUMENT]
    TITLE: StrictDoc
    (newline)

``DOCUMENT`` declaration must always have a ``TITLE`` field. It can have
optional configuration fields and an optional ``[FREETEXT]`` block.

.. code-block:: text

    [DOCUMENT]
    TITLE: StrictDoc

    [FREETEXT]
    StrictDoc is software for writing technical requirements and specifications.
    [/FREETEXT]

Supported configuration fields:

``SPECIAL_FIELDS`` (see Requirement / Special fields below).
[/FREETEXT]

[/SECTION]

[SECTION]
TITLE: Requirement

[FREETEXT]
Minimal "Hello World" program with 3 empty requirements:

.. code-block:: text

    [DOCUMENT]
    TITLE: StrictDoc

    [REQUIREMENT]

    [REQUIREMENT]

    [REQUIREMENT]

Supported fields:

- ``UID`` (unique identifier)
- ``SPECIAL_FIELDS``
- ``REFS``
- ``TITLE``
- ``STATEMENT``
- ``RATIONALE``
- ``COMMENT`` (multiple comments are possible)

Currently, all ``[REQUIREMENT]``'s are optional but most of the time at least
the ``STATEMENT:`` field must be present as well as the ``TITLE:`` field.

.. code-block:: text

    [DOCUMENT]
    TITLE: StrictDoc

    [REQUIREMENT]
    TITLE: Requirements management
    STATEMENT: StrictDoc shall enable requirements management.

**Observation:** Many real-world documents have requirements with statements and
titles but some documents only use statements without title in which case their
title becomes their UID. Example:

.. code-block:: text

    [DOCUMENT]
    TITLE: StrictDoc

    [REQUIREMENT]
    UID: REQ-001
    STATEMENT: StrictDoc shall enable requirements management.
[/FREETEXT]

[SECTION]
TITLE: UID

[FREETEXT]
**Observation:** Some documents do not use unique identifiers which makes it
impossible to trace their requirements to each other. Within StrictDoc's
framework, it is assumed that a good requirements document has all of its
requirements uniquely identifiable, however, the ``UID`` field is optional to
accommodate for documents without connections between requirements.

StrictDoc does not impose any limitations on the format of a UID. Examples of
typical conventions for naming UIDs:

- ``REQ-001``, ``SCA-001`` (scalability), ``PERF-001`` (performance), etc.
- ``cES1008``, ``cTBL6000.1`` (example from NASA cFS requirements)
- Requirements without a number, e.g. ``SDOC-HIGH-DATA-MODEL`` (StrictDoc)
- ``SAVOIR.OBC.PM.80`` (SAVOIR guidelines)

.. code-block:: text

    [DOCUMENT]
    TITLE: StrictDoc

    [REQUIREMENT]
    UID: SDOC-HIGH-DATA-MODEL
    STATEMENT: STATEMENT: StrictDoc shall be based on a well-defined data model.
[/FREETEXT]

[/SECTION]

[SECTION]
TITLE: References

[FREETEXT]
The ``[REQUIREMENT]`` / ``REFS:`` field is used to connect requirements to each
other:

.. code-block:: text

    [DOCUMENT]
    TITLE: StrictDoc

    [REQUIREMENT]
    UID: REQ-001
    STATEMENT: StrictDoc shall enable requirements management.

    [REQUIREMENT]
    UID: REQ-002
    REFS:
    - TYPE: Parent
      VALUE: REQ-001
    TITLE: Requirement #2's title
    STATEMENT: Requirement #2 statement

**Note:** The ``TYPE: Parent`` is the only supported type of connection. In the
future, linking requirements to files will be possible.

**Note:** By design, StrictDoc will only show parent or child links if both
requirements connected with a reference have ``UID`` defined.
[/FREETEXT]

[/SECTION]

[SECTION]
TITLE: Comment

[FREETEXT]
A requirement can have one or more comments explaining this requirement. The
comments can be single-line or multiline.

.. code-block:: text

    [DOCUMENT]
    TITLE: StrictDoc

    [REQUIREMENT]
    UID: REQ-001
    STATEMENT: StrictDoc shall enable requirements management.
    COMMENT: Clarify the meaning or give additional information here.
    COMMENT: >>>
    This is a multiline comment.

    The content is split via \n\n.

    Each line is rendered as a separate paragraph.
    <<<
[/FREETEXT]

[/SECTION]

[SECTION]
TITLE: Rationale

[FREETEXT]
A requirement can have a ``RATIONALE:`` field that explains why such a
requirement exists. Like comments, the rationale field can be single-line or
multiline.

.. code-block:: text

    [DOCUMENT]
    TITLE: StrictDoc

    [REQUIREMENT]
    UID: REQ-001
    STATEMENT: StrictDoc shall enable requirements management.
    COMMENT: Clarify the meaning or give additional information here.
    RATIONALE: The presence of the REQ-001 is justified.
[/FREETEXT]

[/SECTION]

[SECTION]
TITLE: Special fields

[FREETEXT]
**Observation:** Different industries have their own types of requirements
documents. These documents often have specialized meta information which is
different from industry to industry. Example: ``ECSS_VERIFICATION`` field in the
European space industry or ``ASIL`` in the automotive industry.

StrictDoc allows extending its grammar with custom fields that are specific to
a particular document.

First, such fields have to be registered on a document level using the
``SPECIAL_FIELDS`` field:

.. code-block:: text

    [DOCUMENT]
    TITLE: StrictDoc
    SPECIAL_FIELDS:
    - NAME: ASIL
      TYPE: String
    - NAME: ECSS_VERIFICATION
      TYPE: String
      REQUIRED: Yes

This registration adds these fields to the parser that will recognize them
as special fields defined by a user. Declaring a special field as
``REQUIRED: Yes`` makes this field mandatory for each and every requirement in
the document.

When the fields are registered on the document level, it becomes possible to
declare them as the ``[REQUIREMENT]`` special fields:

.. code-block:: text

    [DOCUMENT]
    TITLE: StrictDoc

    [REQUIREMENT]
    UID: REQ-001
    SPECIAL_FIELDS:
      ASIL: D
      ECSS_VERIFICATION: R,A,I,T
    STATEMENT: StrictDoc shall enable requirements management.

**Note:** The ``TYPE: String`` is the only supported type of a special field. In
the future, more specialized types are envisioned, such as ``Int``, ``Enum``,
``Tag``.
[/FREETEXT]

[/SECTION]

[/SECTION]

[SECTION]
TITLE: Section

[FREETEXT]
The ``[SECTION]`` element is used for creating document chapters and grouping
requirements into logical groups. It is equivalent to the use of ``#``, ``##``,
``###``, etc., in Markdown and ``====``, ``----``, ``~~~~`` in RST.

.. code-block:: text

    [DOCUMENT]
    TITLE: StrictDoc

    [SECTION]
    TITLE: High-level requirements

    [REQUIREMENT]
    UID: HIGH-001
    STATEMENT: ...

    [/SECTION]

    [SECTION]
    TITLE: Implementation requirements

    [REQUIREMENT]
    UID: IMPL-001
    STATEMENT: ...

    [/SECTION]
[/FREETEXT]

[SECTION]
TITLE: Nesting sections

[FREETEXT]
Sections can be nested within each other.

.. code-block:: text

    [DOCUMENT]
    TITLE: StrictDoc

    [SECTION]
    TITLE: Chapter

    [SECTION]
    TITLE: Subchapter

    [REQUIREMENT]
    STATEMENT: ...

    [/SECTION]

    [/SECTION]

StrictDoc creates section numbers automatically. In the example above, the
sections will have their titles numbered accordingly: ``1 Chapter`` and
``1.1 Subchapter``.
[/FREETEXT]

[/SECTION]

[SECTION]
TITLE: Free text

[FREETEXT]
A section can have a block of ``[FREETEXT]`` connected to it:

.. code-block:: text

    [DOCUMENT]
    TITLE: StrictDoc

    [SECTION]
    TITLE: Free text

    [FREETEXT]
    A sections can have a block of ``[FREETEXT]`` connected to it:

    ...
    [/FREETEXT]

    [/SECTION]

According to the Strict Rule #2, arbitrary content cannot be written outside
of StrictDoc's grammar structure. ``[SECTION] / [FREETEXT]`` is therefore a
designated grammar element for writing free text content.

**Note:** Free text can also be called "nonnormative" or "informative" text
because it does not contribute anything to the traceability information of the
document. The nonnormative text is there to give a context to the reader and
help with the conceptual understanding of the information. If a certain
information influences or is influenced by existing requirements, it has to be
promoted to the requirement level: the information has to be broken down into
atomic ``[REQUIREMENT]`` statements and get connected to the other requirement
statements in the document.
[/FREETEXT]

[/SECTION]

[/SECTION]

[SECTION]
TITLE: Composite requirement

[FREETEXT]
A ``[COMPOSITE_REQUIREMENT]`` is a requirement that combines requirement
properties of a ``[REQUIREMENT]`` element and grouping features of a ``[SECTION]``
element. This element can be useful in lower-level specifications documents
where a given section of a document has to describe a single feature and the
description requires a one or more levels of nesting. In this case, it might be
natural to use a composite requirement that is tightly connected to a few
related sub-requirements.

.. code-block:: text

    [COMPOSITE_REQUIREMENT]
    STATEMENT: Statement

    [REQUIREMENT]
    STATEMENT: Substatement #1

    [REQUIREMENT]
    STATEMENT: Substatement #2

    [REQUIREMENT]
    STATEMENT: Substatement #3

    [/COMPOSITE_REQUIREMENT]

Special feature of ``[COMPOSITE_REQUIREMENT]``: like ``[SECTION]`` element, the
``[COMPOSITE_REQUIREMENT]`` elements can be nested within each other. However,
``[COMPOSITE_REQUIREMENT]`` cannot nest sections.

**Note:** Composite requirements should not be used in every document. Most
often, a more basic combination of nested ``[SECTION]`` and ``[REQUIREMENT]``
elements should do the job.
[/FREETEXT]

[/SECTION]

[/SECTION]

[/SECTION]

[SECTION]
TITLE: Export options

[SECTION]
TITLE: HTML documentation tree by StrictDoc

[FREETEXT]
This is a default export option supported by StrictDoc.

The following command creates an HTML export:

.. code-block:: text

    strictdoc export docs/ --formats=html --output-dir output-html

**Example:** This documentation is exported by StrictDoc to HTML:
`StrictDoc HTML export <https://strictdoc.readthedocs.io/en/latest/strictdoc-html>`_.

**Note:** The options ``--formats=html`` and ``--output-dir output-html`` can be
skipped because HTML export is a default export option and the default output
folder is ``output``.
[/FREETEXT]

[SECTION]
TITLE: Standalone HTML pages (experimental)

[FREETEXT]
The following command creates a normal HTML export with all pages having their
assets embedded into HTML using Data URI / Base64:

.. code-block:: text

    strictdoc export docs/ --formats=html-standalone --output-dir output-html

The generated document are self-contained HTML pages that can be shared via
email as single files. This option might be especially useful if you work with
a single document instead of a documentation tree with multiple documents.
[/FREETEXT]

[/SECTION]

[/SECTION]

[SECTION]
TITLE: HTML export via Sphinx

[FREETEXT]
The following command creates an RST export:

.. code-block:: text

    strictdoc export YourDoc.sdoc --formats=rst --output-dir output

The created RST files can be copied to a project created using Sphinx, see
`Getting Started with Sphinx <https://docs.readthedocs.io/en/stable/intro/getting-started-with-sphinx.html>`_.

.. code-block:: text

    cp -v output/YourDoc.rst docs/sphinx/source/
    cd docs/sphinx && make html

`StrictDoc's own Sphinx/HTML documentation
<https://strictdoc.readthedocs.io/en/latest/>`_
is generated this way, see the Invoke task:
`invoke sphinx <https://github.com/strictdoc-project/strictdoc/blob/5c94aab96da4ca21944774f44b2c88509be9636e/tasks.py#L48>`_.
[/FREETEXT]

[/SECTION]

[SECTION]
TITLE: PDF export via Sphinx/LaTeX

[FREETEXT]

The following command creates an RST export:

.. code-block:: text

    strictdoc export YourDoc.sdoc --formats=rst --output-dir output

The created RST files can be copied to a project created using Sphinx, see
`Getting Started with Sphinx <https://docs.readthedocs.io/en/stable/intro/getting-started-with-sphinx.html>`_.

.. code-block:: text

    cp -v output/YourDoc.rst docs/sphinx/source/
    cd docs/sphinx && make pdf

`StrictDoc's own Sphinx/PDF documentation
<https://strictdoc.readthedocs.io/_/downloads/en/latest/pdf/>`_
is generated this way, see the Invoke task:
`invoke sphinx <https://github.com/strictdoc-project/strictdoc/blob/5c94aab96da4ca21944774f44b2c88509be9636e/tasks.py#L48>`_.
[/FREETEXT]

[/SECTION]

[/SECTION]

[SECTION]
TITLE: Options

[SECTION]
TITLE: Parallelization

[FREETEXT]
To improve performance for the large document trees (1000+ requirements),
StrictDoc parallelizes reading and generation of the documents using
process-based parallelization: ``multiprocessing.Pool`` and
``multiprocessing.Queue``.

Parallelization improves performance but can also complicate understanding
behavior of the code if something goes wrong.

To disable parallelization use the ``--no-parallelization`` option:

.. code-block:: text

    strictdoc export --no-parallelization docs/

**Note:** Currently, only the generation of HTML documents is parallelized, so
this option will only have effect on the HTML export. All other export options
are run from the main thread. Reading of the SDoc documents is parallelized for
all export options and is disabled with this option as well.
[/FREETEXT]

[/SECTION]

[/SECTION]

[SECTION]
TITLE: StrictDoc and other tools

[SECTION]
TITLE: StrictDoc and Doorstop

[FREETEXT]
The StrictDoc project is a close successor of another project called
`Doorstop <https://github.com/doorstop-dev/doorstop>`_.

    Doorstop is a requirements management tool that facilitates the storage of
    textual requirements alongside source code in version control.

The author of Doorstop has published a `paper about Doorstop <http://www.scirp.org/journal/PaperInformation.aspx?PaperID=44268#.UzYtfWRdXEZ>`_
where the rationale behind text-based requirements management is provided.

The first version of StrictDoc had started as a fork of the Doorstop project.
However, after a while, the StrictDoc was started from scratch as a separate
project. At this point, StrictDoc and Doorstop do not share any code but
StrictDoc still shares with Doorstop their common underlying design principles:

- Both Doorstop and StrictDoc are written using Python. Both are pip packages which are easy-to-install.
- Both Doorstop and StrictDoc provide a command-line interface.
- Both Doorstop and StrictDoc use text files for requirements management.
- Both Doorstop and StrictDoc encourage collocation of code and documentation.
  When documentation is hosted close to code it has less chances of diverging
  from the actual implementation or becoming outdated.
- As the free and open source projects, both Doorstop and StrictDoc seem to
  struggle to find resources for development of specialized GUI interfaces this
  is why both tools give a preference to supporting exporting documentation
  pages to HTML format as the primary export feature.

StrictDoc differs from Doorstop in a number of aspects:

- Doorstop stores requirements in YAML files, one separate file per requirement
  (`example <https://github.com/doorstop-dev/doorstop/blob/804153c67c7c5466ee94e9553118cc3df03a56f9/reqs/REQ001.yml>`_).
  The document in Doorstop is assembled from the requirements files into a
  single logical document during the document generation process.
  StrictDoc's documentation unit is one document stored in an .sdoc file. Such a
  document can have multiple requirements grouped by sections.
- In YAML files, Doorstop stores requirements properties such as
  ``normative: true`` or ``level: 2.3`` for which Doorstop provides validations.
  Such a design decision, in fact, assumes an existence of implicitly-defined
  grammar which is encoded "ad-hoc" in the parsing and validation rules of
  Doorstop.
  StrictDoc takes a different approach and defines its grammar explicitly using
  a tool for creating Domain-Specific Languages called `textX <https://github.com/textX/textX>`_.
  TextX support allows StrictDoc to encode a strict type-safe grammar in a
  `single grammar file <https://github.com/strictdoc-project/strictdoc/blob/93486a0e9fb30b141187587eae9e995cd86c6cbf/strictdoc/backend/dsl/grammar.py>`_
  that StrictDoc uses to parse the documentation files
  using the parsing capabilities provided by textX out of the box.

The roadmap of StrictDoc contains a work item for supporting the export/import
to/from Doorstop format.
[/FREETEXT]

[/SECTION]

[SECTION]
TITLE: StrictDoc and Sphinx

[FREETEXT]
Both Sphinx and StrictDoc are both documentation generators but StrictDoc is at
a higher level of abstraction: StrictDoc's specialization is requirements and
specifications documents. StrictDoc can generate documentation to a number of
formats including HTML format as well as the RST format which is a default
input format for Sphinx. A two stage generation is therefore possible:
StrictDoc generates RST documentation which then can be generated to HTML, PDF,
and other formats using Sphinx.

If you are reading this documentation at
https://strictdoc.readthedocs.io/en/latest
then you are already looking at the example: this documentation stored in
`strictdoc.sdoc <https://github.com/strictdoc-project/strictdoc/blob/master/docs/strictdoc.sdoc>`_
is converted to RST format by StrictDoc which is further converted to the HTML
website by readthedocs which uses Sphinx under the hood. The
``StrictDoc -> RST -> Sphinx -> PDF`` example is also generated using readthedocs:
`StrictDoc <https://strictdoc.readthedocs.io/_/downloads/en/latest/pdf/>`_.
[/FREETEXT]

[/SECTION]

[SECTION]
TITLE: StrictDoc and Sphinx-Needs

[FREETEXT]
`Sphinx-Needs <https://sphinxcontrib-needs.readthedocs.io/en/latest/>`_ is a
text-based requirements management system based on Sphinx. It is implemented
as a Sphinx extension that extends the
`reStructuredText (RST)
<https://docutils.sourceforge.io/docs/user/rst/quickref.html>`_
markup language with additional syntax for writing requirements documents.

Sphinx-Needs was a great source of inspiration for the second version of
StrictDoc which was first implemented as a Sphinx extension and then as a more
independent library on top of `docutils <https://docutils.sourceforge.io/>`_
that Sphinx uses for the underlying RST syntax processing work.

The similarities between Sphinx-Needs and StrictDoc:

- In contrast to Doorstop, both Sphinx-Needs and StrictDoc do not split a
  document into many small files, one file per single requirement (see
  discussion
  `doorstop#401 <https://github.com/doorstop-dev/doorstop/issues/401>`_). Both
  tools follow the "file per document" approach.
- Sphinx-Needs has a
  `well-developed language
  <https://sphinxcontrib-needs.readthedocs.io/en/latest/directives/index.html>`_
  based on custom RST directives, such
  as ``req::``, ``spec::``, ``needtable::``, etc. The RST document is parsed
  by Sphinx/docutils into RST abstract syntax tree (AST) which allows creating
  an object graph out for the documents and their requirements from the RST
  document. StrictDoc uses textX for building an AST from a SDoc document.
  Essentially, both Sphinx-Needs and StrictDoc works in a similar way but use
  different markup languages and tooling for the job.

The difference between Sphinx-Needs and StrictDoc:

- RST tooling provided by Sphinx/docutils is very powerful, yet it can also be
  rather limiting. The RST syntax and underlying docutils tooling do not allow
  much flexibility needed for creating a language for defining requirements
  using a custom and explicit grammar, a feature that became a cornerstone of
  StrictDoc. This was a major reason why the third generation of
  StrictDoc started with a migration from docutils to
  `textX <https://github.com/textX/textX>`_ which is a
  dedicated tool for creating custom Domain-Specific Languages. After the
  migration to textX, StrictDoc is no longer restricted to the limitations of
  the RST document, while it is still possible to generate SDoc files to RST
  using StrictDoc and then further generate RST to HTML/PDF and other formats
  using Sphinx.
- Sphinx-Needs has an impressive list of config options and features that
  StrictDoc is missing. Examples: Customizing the look of the requirements,
  `Roles <https://sphinxcontrib-needs.readthedocs.io/en/latest/roles.html>`_,
  `Services
  <https://sphinxcontrib-needs.readthedocs.io/en/latest/services/index.html>`_
  and
  `others
  <https://sphinxcontrib-needs.readthedocs.io/en/latest/index.html>`_.
[/FREETEXT]

[/SECTION]

[/SECTION]

[SECTION]
TITLE: StrictDoc Requirements

[SECTION]
TITLE: Project goals

[REQUIREMENT]
UID: GOAL-1-TOOL-SUPPORT
TITLE: Software support for writing requirements and specifications documents
STATEMENT: >>>
There shall exist free and lightweight yet capable software for writing
requirements and specifications documents
<<<
COMMENT: >>>
Technical documentation is hard, it can be an extremely laborious process.
Software shall support engineers in their work with documentation.
<<<
COMMENT: >>>
The state of the art for many small companies working with
requirements: using Excel for requirements management in the projects with
hundreds or thousands of requirements.
<<<

[REQUIREMENT]
UID: GOAL-2-REDUCE-DOCUMENTATION-HAZARDS
TITLE: Reduce documentation hazards
STATEMENT: >>>
There shall exist no (or less) opportunity for writing incorrect or inconsistent
documentation.
<<<
COMMENT: >>>
Every serious engineering activity, such as safety engineering or systems
engineering, starts with requirements. The more critical is a product the higher
the importance of good documentation.

Technical documentation can be and often becomes a source of hazards.
It is recognized that many failures stem from inadequate requirements
engineering. While it is not possible to fix the problem of inadequate
requirements engineering in general, it is definitely possible to improve
software that supports engineers in activities such as requirements engineering
and writing technical documentation.
<<<

[REQUIREMENT]
UID: GOAL-3-NO-RUNAWAY-DOCUMENTATION
TITLE: No (or less) run-away documentation
STATEMENT: Software shall support engineers in keeping documentation up-to-date.
COMMENT: >>>
Technical documentation easily becomes outdated. Many existing tools for
documentation do not provide any measures for ensuring overall consistency of
documents and documentation trees.
<<<

[REQUIREMENT]
UID: GOAL-4-CHANGE-MANAGEMENT
TITLE: Change management
STATEMENT: Software shall provide capabilities for change management and impact assessment.
COMMENT: >>>
Change management is difficult. The bigger the project is, the harder it is to
maintain its documentation. If a change is introduced to a project, it usually
requires a full revision of its requirements.
<<<
COMMENT: >>>
When the basic capabilities of StrictDoc are in place, it should be possible
to do a more advanced analysis of requirements and requirement trees:

- Finding similar or relevant requirements.
- Enforce invariants that should be hold. Example: mass or power budget.
<<<

[/SECTION]

[SECTION]
TITLE: High-level requirements

[REQUIREMENT]
UID: SDOC-HIGH-REQS-MANAGEMENT
REFS:
- TYPE: Parent
  VALUE: GOAL-1-TOOL-SUPPORT
TITLE: Requirements management
STATEMENT: StrictDoc shall enable requirements management.

[REQUIREMENT]
UID: SDOC-HIGH-DATA-MODEL
TITLE: Data model
STATEMENT: StrictDoc shall be based on a well-defined data model.
COMMENT: >>>
StrictDoc is a result of several attempts to find a solution for working with
text-based requirements:

- StrictDoc, first generation: Markdown-based C++ program. Custom requirements
  metadata in YAML.
- StrictDoc, second generation: RST/Sphinx-based Python program. Using Sphinx
  extensions to manage meta information.

The result of these efforts was the realization that a text-based requirements
and specifications management tool could be built on top of a domain-specific
language (DSL) created specifically for the purpose of writing requirements and
specifications documents. Such a language allows an explicit definition of a
document data model which is called "grammar".
<<<

[REQUIREMENT]
TITLE: Command-line interface
STATEMENT: StrictDoc shall provide a command-line interface.

[COMPOSITE_REQUIREMENT]
TITLE: Platform support
STATEMENT: StrictDoc shall work on all major platforms.

[REQUIREMENT]
TITLE: macOS support
STATEMENT: StrictDoc shall work on macOS systems.

[REQUIREMENT]
TITLE: Linux support
STATEMENT: StrictDoc shall work on Linux systems.

[REQUIREMENT]
TITLE: Windows support
STATEMENT: StrictDoc shall work on Windows systems.

[/COMPOSITE_REQUIREMENT]

[REQUIREMENT]
TITLE: Requirements validation
STATEMENT: StrictDoc shall allow validation of requirement documents.

[REQUIREMENT]
TITLE: Requirements text format
STATEMENT: StrictDoc shall allow storage of requirements in a plain-text human readable form.

[REQUIREMENT]
TITLE: Linking requirements
STATEMENT: StrictDoc shall support linking requirements to each other.

[REQUIREMENT]
TITLE: Scalability
STATEMENT: StrictDoc shall allow working with large documents and document trees containing at least 10000 requirement items.

[REQUIREMENT]
UID: SDOC-HIGH-REQS-TRACEABILITY
TITLE: Traceability
STATEMENT: StrictDoc shall support traceability of requirements.

[REQUIREMENT]
TITLE: Visualization
STATEMENT: StrictDoc shall provide means for visualization of requirement documents.

[REQUIREMENT]
TITLE: Open source software
STATEMENT: StrictDoc shall always be free and open source software.

[/SECTION]

[SECTION]
TITLE: Implementation requirements

[REQUIREMENT]
UID: SDOC-IMPL-PARAL
TITLE: Parallelization
STATEMENT: StrictDoc shall enable parallelization of the time-consuming parts of the code.

[REQUIREMENT]
UID: SDOC-IMPL-INCREMENTAL
TITLE: Incremental generation
STATEMENT: StrictDoc shall enable incremental generation of the documents.
COMMENT: >>>
When exporting documentation tree, StrictDoc shall regenerate only changed
documents and files.
<<<

[/SECTION]

[SECTION]
TITLE: Data model

[REQUIREMENT]
UID: SDOC-DM-MODEL
REFS:
- TYPE: Parent
  VALUE: SDOC-HIGH-REQS-MANAGEMENT
- TYPE: Parent
  VALUE: SDOC-HIGH-DATA-MODEL
TITLE: Modeling capability
STATEMENT: StrictDoc's Data Model shall accommodate for maximum possible standard requirement document formats.
COMMENT: >>>
Examples of standard requirements documents include but are not limited to:

- Non-nested requirement lists split by categories
  (e.g., Functional Requirements, Interface Requirements, Performance Requirements, etc.)
<<<

[SECTION]
TITLE: Section item

[/SECTION]

[SECTION]
TITLE: Requirement item

[REQUIREMENT]
TITLE: Statement
STATEMENT: Requirement item shall have a statement.

[REQUIREMENT]
TITLE: Content body
STATEMENT: Requirement item might have an content body.

[COMPOSITE_REQUIREMENT]
TITLE: UID identifier
STATEMENT: Requirement item might have an UID identifier.

[REQUIREMENT]
TITLE: UID identifier format
STATEMENT: StrictDoc shall not impose any restrictions on the UID field format.
COMMENT: >>>
Conventions used for requirement UIDs can be very different. And there seems to
be no way to define a single rule.

Some examples:

- FUN-003
- cES1008, cTBL6000.1 (NASA cFS)
- Requirements without a number, e.g. SDOC-HIGH-DATA-MODEL (StrictDoc)
- SAVOIR.OBC.PM.80 (SAVOIR)
<<<

[/COMPOSITE_REQUIREMENT]

[REQUIREMENT]
TITLE: Title
STATEMENT: Requirement item might have an title.

[REQUIREMENT]
TITLE: References
STATEMENT: Requirement item might have one or more references.

[REQUIREMENT]
TITLE: Comments
STATEMENT: Requirement item might have one or more comments.

[REQUIREMENT]
TITLE: Special fields
STATEMENT: StrictDoc shall support customization of the default Requirement's grammar with special fields.
COMMENT: >>>
Examples:

- RAIT compliance fields (Review of design, analysis, inspection, testing)
- Automotive Safety Integrity Level level (ASIL).
<<<

[/SECTION]

[SECTION]
TITLE: Composite Requirement item

[FREETEXT]
TBD
[/FREETEXT]

[/SECTION]

[COMPOSITE_REQUIREMENT]
TITLE: Links
STATEMENT: StrictDoc's data model shall support linking document content nodes to each other.

[REQUIREMENT]
TITLE: Parent links
STATEMENT: StrictDoc's data model shall support linking a requirement to another requirement using PARENT link.

[/COMPOSITE_REQUIREMENT]

[/SECTION]

[SECTION]
TITLE: SDOC file format

[REQUIREMENT]
UID: SDOC-FMT-PRIMARY
REFS:
- TYPE: Parent
  VALUE: SDOC-DM-MODEL
TITLE: Primary text implementation
STATEMENT: SDOC format shall support encoding the Strict Doc Data Model in a plain-text human readable form.

[REQUIREMENT]
UID: SDOC-FMT-GRAMMAR
REFS:
- TYPE: Parent
  VALUE: SDOC-HIGH-DATA-MODEL
TITLE: Grammar
STATEMENT: SDOC format shall be based on a fixed grammar.

[REQUIREMENT]
TITLE: Type safety
STATEMENT: SDOC format shall allow type-safe encoding of requirement documents.

[/SECTION]

[SECTION]
TITLE: Document Generators

[SECTION]
TITLE: HTML Export

[REQUIREMENT]
TITLE: Single document: Normal form
STATEMENT: StrictDoc shall export single document pages in a normal document-like form.

[REQUIREMENT]
TITLE: Single document: Tabular form
STATEMENT: StrictDoc shall export single document pages in a tabular form.

[REQUIREMENT]
REFS:
- TYPE: Parent
  VALUE: SDOC-HIGH-REQS-TRACEABILITY
TITLE: Single document: 1-level traceability
STATEMENT: StrictDoc shall export 1-level traceability document.

[REQUIREMENT]
REFS:
- TYPE: Parent
  VALUE: SDOC-HIGH-REQS-TRACEABILITY
TITLE: Single document: Deep traceability
STATEMENT: StrictDoc shall export deep traceability document.

[REQUIREMENT]
TITLE: Left panel: Table of contents
STATEMENT: StrictDoc shall export all HTML pages with Table of Contents.

[/SECTION]

[SECTION]
TITLE: PDF Export

[REQUIREMENT]
TITLE: Sphinx documentation generator
STATEMENT: StrictDoc shall support exporting documents to Sphinx/RST format.

[/SECTION]

[REQUIREMENT]
TITLE: Excel Export
STATEMENT: StrictDoc shall support exporting documents to Excel format.

[/SECTION]

[SECTION]
TITLE: Validation requirements

[REQUIREMENT]
TITLE: Valid HTML markup
STATEMENT: StrictDoc's HTML export tests shall validate the generated HTML markup.
COMMENT: First candidate: Table of contents and its nested ``<ul>/<li>`` items.

[/SECTION]

[/SECTION]

[SECTION]
TITLE: Design decisions

[SECTION]
TITLE: Building blocks

[REQUIREMENT]
TITLE: TextX
STATEMENT: TextX shall be used for StrictDoc grammar definition and parsing of the sdoc files.
COMMENT: >>>
TextX is an easy-to-install Python tool. It is fast, works out of the box.
<<<

[REQUIREMENT]
TITLE: Jinja2
STATEMENT: Jinja2 shall be used for rendering HTML templates.

[REQUIREMENT]
TITLE: Sphinx and Docutils
STATEMENT: >>>
Sphinx and Docutils shall be used for the following capabilities:

- Support of Restructured Text (reST) format
- Generation of RST documents into HTML
- Generation of RST documents into PDF using LaTeX
- Generating documentation websites using Sphinx
<<<

[/SECTION]

[SECTION]
TITLE: SDoc grammar

[REQUIREMENT]
TITLE: No indentation
STATEMENT: SDoc grammar's building blocks shall not allow any indentation.
COMMENT: >>>
Rationale: Adding indentation to any of the fields does not scale well when the
documents have deeply nested section structure as well as when the size of the
paragraphs becomes sufficiently large. Keeping every keyword like [REQUIREMENT]
or [COMMENT] with no indentation ensures that one does not have to think about
possible indentation issues.
<<<

[/SECTION]

[/SECTION]

[SECTION]
TITLE: Backlog

[REQUIREMENT]
TITLE: Generated file names
STATEMENT: StrictDoc shall preserve original document file names when generating to all export formats.
COMMENT: >>>
StrictDoc used to create file names that were document names. This has been
changed for HTML but not yet for RST.
<<<

[REQUIREMENT]
TITLE: Validation: Uniqueness of UID identifiers in a document tree
STATEMENT: StrictDoc shall ensure that each UID used in a document tree is unique.
COMMENT: This is implemented but the error message shall be made more readable.

[REQUIREMENT]
TITLE: StrictDoc as library
STATEMENT: StrictDoc shall support it use as a Python library.
COMMENT: >>>
Such a use allows a more fine-grained access to the StrictDoc's modules, such
as Grammar, Import, Export classes, etc.
<<<

[REQUIREMENT]
UID: BACKLOG-FUZZY-SEARCH
REFS:
- TYPE: Parent
  VALUE: GOAL-4-CHANGE-MANAGEMENT
TITLE: Fuzzy requirements search
STATEMENT: StrictDoc shall support finding relevant requirements.
COMMENT: >>>
This feature can be implemented in the CLI as well as in the future GUI. A fuzzy
requirements search can help to find existing requirements and also identify
relevant requirements when creating new requirements.
<<<

[SECTION]
TITLE: Export capabilities

[REQUIREMENT]
TITLE: CSV import/export
STATEMENT: StrictDoc shall support exporting documents to CSV format.

[REQUIREMENT]
TITLE: PlantUML export
STATEMENT: StrictDoc shall support exporting documents to PlantUML format.

[REQUIREMENT]
TITLE: ReqIF import/export
STATEMENT: StrictDoc shall support ReqIF format.

[REQUIREMENT]
TITLE: Confluence import/export
STATEMENT: StrictDoc shall support importing/exporting documents from/to Confluence HTML storage format.

[REQUIREMENT]
TITLE: Tex export
STATEMENT: StrictDoc shall support exporting documents to Tex format.

[REQUIREMENT]
TITLE: Doorstop import/export
STATEMENT: >>>
StrictDoc shall support import and exporting documents from/to
`Doorstop <https://github.com/doorstop-dev/doorstop>`_ format.
<<<

[REQUIREMENT]
TITLE: Markdown support for text and code blocks
STATEMENT: StrictDoc shall support rendering text/code blocks into Markdown syntax.

[/SECTION]

[SECTION]
TITLE: Traceability and coverage

[REQUIREMENT]
TITLE: Linking with implementation artifacts
STATEMENT: StrictDoc shall support linking requirements to files.

[REQUIREMENT]
TITLE: Requirement checksumming
STATEMENT: StrictDoc shall support calculation of checksums for requirements.

[REQUIREMENT]
TITLE: Documentation coverage
STATEMENT: StrictDoc shall generate requirements coverage information.

[/SECTION]

[REQUIREMENT]
TITLE: Filtering by tags
STATEMENT: StrictDoc shall support filtering filtering by tags.

[SECTION]
TITLE: Advanced

[REQUIREMENT]
TITLE: Facts table. Invariants calculation.
STATEMENT: >>>
StrictDoc shall support creation of fact tables and allow calculation of
invariants for constraints enforcement.
<<<

[REQUIREMENT]
TITLE: FMEA/FMECA tables
STATEMENT: >>>
StrictDoc shall support creation of FMEA/FMECA safety analysis documents.
<<<

[REQUIREMENT]
TITLE: Graphical User Interface (GUI)
STATEMENT: StrictDoc shall provide a Graphical User Interface (GUI).

[REQUIREMENT]
TITLE: Web server and editable HTML pages
STATEMENT: >>>
StrictDoc shall provide a web server that serves as a StrictDoc backend for
reading and writing SDoc files.
<<<

[/SECTION]

[/SECTION]
