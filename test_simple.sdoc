[DOCUMENT]
TITLE: Simple Test Document

[REQUIREMENT]
UID: TES-1
STATUS: Draft
TITLE: Simple Test Document
STATEMENT: This requirement covers Simple Test Document.
RATIONALE: Converted from original document structure.

[REQUIREMENT]
UID: TES-2
STATUS: Draft
TITLE: 1. Scope
STATEMENT: This requirement covers 1. Scope.
RATIONALE: Converted from original document structure.

[REQUIREMENT]
UID: TES-3
STATUS: Draft
TITLE: 1.1 Identification
STATEMENT: This requirement covers 1.1 Identification.
RATIONALE: Converted from original document structure.

[REQUIREMENT]
UID: TES-4
STATUS: Draft
TITLE: Test Requirement
STATEMENT: This requirement covers Test Requirement.
RATIONALE: Converted from original document structure.
