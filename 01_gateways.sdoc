[DOCUMENT]
TITLE: Vehicle Network Gateway Devices Security Requirements

[GRAMMAR]
ELEMENTS:
- TAG: REQUIREMENT
  FIELDS:
  - TITLE: UID
    TYPE: String
    REQUIRED: True
  - TITLE: LEVEL
    TYPE: String
    REQUIRED: False
  - TITLE: STATUS
    TYPE: String
    REQUIRED: False
  - TITLE: REFS
    TYPE: String
    REQUIRED: False
  - TITLE: TITLE
    TYPE: String
    REQUIRED: False
  - TITLE: STATEMENT
    TYPE: String
    REQUIRED: False
  - TITLE: TAGS
    TYPE: String
    REQUIRED: False
  - TITLE: RATIONALE
    TYPE: String
    REQUIRED: False
  - TITLE: COMMENT
    TYPE: String
    REQUIRED: False
  - TITLE: PUB_REFS
    TYPE: String
    REQUIRED: False
  - TITLE: VERIFICATION
    TYPE: String
    REQUIRED: False
  - TITLE: CRITICALITY
    TYPE: String
    REQUIRED: False

[FREETEXT]
This document captures security requirements for vehicle network gateway devices: both devices intended to be gateways and those devices which *could be a gateway* (due to malicious code). There will be devices which are connected to multiple vehicle networks but not all of them are intended to perform gatewaying functions. The design intent of the device dictactes what security requirements it must satisfy.

First let us define the two types of network domains (or segments) to which the Gateway devices will connect:

Untrusted Network Domain (*UND*):
    A *UND* is a network domain (or segment) that contains **any** of the following:

    a) wireless communication or reachable wirelessly (e.g J2497, ISO 15118, BlueTooth, WiFi)
    b) an interface for aftermarket devices or operator access (e.g. an OBD port, RP1226 connector)
    c) a telematics device that does not satisfy the HD VCR requirements
    d) a multi-network device (e.g. intended or unintended gateway) that does not satisfy the HD VCR requirements

Trusted Network Domain (*TND*):
    A *TND* is a network domain (or segment) that **does not contain any** of the following:

    a) wireless communication or reachable wirelessly (e.g J2497)
    b) an interface for aftermarket devices or operator access (e.g. an OBD port)
    c) a telematics device that does not satisfy the HD VCR requirements
    d) a multi-network device (e.g. intended or unintended gateway) that does not satisfy the HD VCR requirements

Some Examples of TND and UND:

The RP1226 connector is made for connecting aftermarket devices; therefore the databuses there are UNDs.
::


            ┌───────────────┐                 ┌──────────────┐                     ┌─┐
            │  Gateway sat  │                 │              │                     │┼│
    ────────┤   all HDVCR   ├─────────────────┤    RP1226    ├─────────────────────┼┼│
      TND   │  requirements │     UND         │   Connector  │      UND            │┼│
            └───────────────┘                 └──────────────┘                     └─┘


The OBD connector is _the_ operator access port; therefore the databuses there are UNDs.
::


            ┌───────────────┐                 ┌──────────────┐                     ┌─┐
            │  Gateway sat  │                 │              │                     │┼│
    ────────┤   all HDVCR   ├─────────────────┤      OBD     ├─────────────────────┼┼│
      TND   │  requirements │     UND         │   Connector  │      UND            │┼│
            └───────────────┘                 └──────────────┘                     └─┘

The TPMS gateways on RP1226 databus connect to a wireless medium and are on the aftermarket bus; therefore the databuses there are UNDs.
::


            ┌───────────────┐                 ┌──────────────┐                  ┌──────────────┐
            │  Gateway sat  │                 │              │                  │              │     Wireless
    ────────┤   all HDVCR   ├─────────────────┤    RP1226    ├──────────────────┤     TPMS     ├───────~~)))
      TND   │  requirements │     UND         │   Connector  │      UND         │   Gateway    │      UND
            └───────────────┘                 └──────────────┘                  └──────────────┘


Then we can define (Intended) Gateways

(Intended) Gateway:
    A device which has connections to multiple vehicle network domains (or segments) and performs one or more gateway functions between a Untrusted Network Domain (*UND*) and Trusted Network Domains (*TND*). (Intended) Gateways must satisfy the requirements in section *Security Requirements for Abstract (Intended) Gateways*.

Unintended Gateway:
    A device which has connections to multiple vehicle network domains (or segments) and performs none of the gateway functions. These devices could perform gateway functions (due to malicious code) but are not intended to. Unintended Gateways must satisfy the requirements in section *Security Requirements for Abstract Unintended Gateways*.

The gateway functions that duck type the gateway devices are as follows:

Transports:
    These devices transport/'move' information between two separate network 'domains,' **bi-bidirectionally.**

Translates:
    These devices translate/transform the information between the separate network domains but intentions of the data are preserved.

Filter/Drop/Rate-Limit:
    These devices select which information is transported based on rules matching content or metadata before (ingress) or after (egress) processing steps in preparation for transport/translate/encapsulate or other forwarding actions. These devices select which information is transported in a time varying fashion for the purposes of limiting the rate at which the information is put on a network domain.

Encapsulates:
    These devices encapsulate information as it is transported and/or translated between the network domains.

Note that (Intended) Gateways may optionally perform the following functions as well -- and to do so would be beneficial; however, performing one or more of these functions does not make a device a gateway as were the case with the gateway functions above.

* These devices may be controllable by users with necessary authentication and authorization
* These devices may be configurable by users with necessary authentication and authorization
* These devices may report status of operation to users with necessary authentication and authorization
* These devices may provide diagnostic commands to users with necessary authentication and authorization

Note on options for requirements: This document contains requirements where the working group cannot reasonably require a particular implementation option, only that one of the satisfactory ways to satisfy the requirement is implemented. Modelling these 'options' requirements is not possible nor reccomended: the sheer number of requirements which will be captured for heavy vehicles means that the requirements must remain machine readable and there is no machine readable way to communicate options to implementors (for good reason). The approach that is taken is to a) include the options as notes to the implementers of these requirements and b) to tag all requirements with `CONTAINS_OPTIONS` so the entire list of requirements containing notes to the implementers can be indexed for easy reference by them.
[/FREETEXT]

[SECTION]
TITLE: Security Requirements for Abstract (Intended) Gateways

[FREETEXT]
The following requirements must be satisfied by any device intended to be a gateway on *any type of* vehicle networks. There are CAN-specific and J1939-sepcific requirements in the CGW- and J1939GW- series below.
[/FREETEXT]

[REQUIREMENT]
UID: AGW-S-000
TITLE: Gateway Configuration Protected
STATEMENT: The device SHALL accept and react only to configuration changes which are correctly authorized and authenticated, regardless of origin of network domain.
CRITICALITY: High
PUB_REFS: >>>    
SAE J3061: Appendix F - VEHICLE LEVEL CONSIDERATIONS, Security Mechanisms, b. Access control mechanisms to restrict access to critical ECUs, critical modes of every ECU (diagnostic mode), and their data.
SAE J3061: Appendix F - VEHICLE LEVEL CONSIDERATIONS, Security Mechanisms, g. Mechanisms that effectively secure maintenance operations, including both diagnostic procedures and update procedures.
<<<


[REQUIREMENT]
UID: AGW-S-001
TITLE: Prevents OTA
STATEMENT: The device SHALL prevent Over The Air updates (OTA) (including parameter flash) from *UND* to *TND*, unless with explicitly authorized and authenticated configuration changes via the mode switch.
CRITICALITY: High
PUB_REFS: >>>    
SAE J3061: Appendix F - VEHICLE LEVEL CONSIDERATIONS, Security Mechanisms, b. Access control mechanisms to restrict access to critical ECUs, critical modes of every ECU (diagnostic mode), and their data.
SAE J3061: Appendix F - VEHICLE LEVEL CONSIDERATIONS, Security Mechanisms, g. Mechanisms that effectively secure maintenance operations, including both diagnostic procedures and update procedures.
<<<

[REQUIREMENT]
UID: AGW-S-002
TITLE: Prevents DoS
STATEMENT: The device SHALL prevent generating Denial of Service (DoS) on *TND* from messages originating on *UND*.
CRITICALITY: High
PUB_REFS: >>> 
SAE J3061: Appendix F - VEHICLE LEVEL CONSIDERATIONS, Security Mechanisms, a. Isolation/partitioning of systems that have external access (e.g., Wi Fi, Bluetooth, OBD) from safety-critical systems and systems that can have important impacts on the operation of the vehicle.
<<<

[REQUIREMENT]
UID: AGW-S-003
TITLE: Prevents Spoofing
STATEMENT: The device SHALL prevent spoofing/masquerading/injection onto *TND*
CRITICALITY: High
PUB_REFS: >>> 
SAE J3061: Appendix F - VEHICLE LEVEL CONSIDERATIONS, Security Mechanisms, a. Isolation/partitioning of systems that have external access (e.g., Wi Fi, Bluetooth, OBD) from safety-critical systems and systems that can have important impacts on the operation of the vehicle.
<<<

[REQUIREMENT]
UID: AGW-S-004
TITLE: Prevents Exfiltration
STATEMENT: >>>
The device SHALL prevent exfiltration of data from *TND* to *UND*, or vice-versa, by satisfying one or more of these methods:

* Protect Confidentiality: These devices MAY encapsulate and/or translate (e.g. encrypt) information as it is transported between the network domains for the purposes of protecting confidentiality of the information in the domain to which the information is moved.
* Re-Write / Masking: The device SHALL provide a means of masking or otherwise re-writing data to prevent exfiltration of sensitive information from *TND* to *UND*.

<<<
TAGS: CONTAINS_OPTIONS
CRITICALITY: High
PUB_REFS: >>>
SAE J3061: Appendix F - VEHICLE LEVEL CONSIDERATIONS, Security Mechanisms, c. Access control mechanisms that tend to restrict access to information about the operational state of the vehicle, privacy sensitive information, financially sensitive information, detailed design information, etc.
<<<

[REQUIREMENT]
UID: AGW-S-005
TITLE: Prevents Elevation
STATEMENT: The device SHALL prevent abuse of *TND* network domain functionality from *UND* to *TND*, unless with explicitly authorized and authenticated configuration changes via the mode switch.
CRITICALITY: High
PUB_REFS: >>>
SAE J3061: Appendix F - VEHICLE LEVEL CONSIDERATIONS, Security Mechanisms, a. Isolation/partitioning of systems that have external access (e.g., Wi Fi, Bluetooth, OBD) from safety-critical systems and systems that can have important impacts on the operation of the vehicle.
SAE J3061: Appendix F - VEHICLE LEVEL CONSIDERATIONS, Security Mechanisms, b. Access control mechanisms to restrict access to critical ECUs, critical modes of every ECU (diagnostic mode), and their data.
SAE J3061: Appendix F - VEHICLE LEVEL CONSIDERATIONS, Security Mechanisms, e. Central gateway or domain controller based architectures.
<<<

[REQUIREMENT]
UID: AGW-S-006
TITLE: Prevents Data Loss
STATEMENT: The device SHALL prevent all data loss and/or corruption of information in the bidirectional *UND* ↔ *TND* operation, unless with explicit configuration for rate limiting (AGW-F-006) or translation (AGW-F-002).
CRITICALITY: High

[REQUIREMENT]
UID: AGW-S-007
TITLE: Preserves High Side Operation
STATEMENT: The device SHALL prevent degradation of any *TND* operation due to *UND* activity.
CRITICALITY: High
PUB_REFS: >>>
SAE J3061: Appendix F - VEHICLE LEVEL CONSIDERATIONS, Security Mechanisms, a. Isolation/partitioning of systems that have external access (e.g., Wi Fi, Bluetooth, OBD) from safety-critical systems and systems that can have important impacts on the operation of the vehicle.
SAE J3061: Appendix F - VEHICLE LEVEL CONSIDERATIONS, Security Mechanisms, b. Access control mechanisms to restrict access to critical ECUs, critical modes of every ECU (diagnostic mode), and their data.
SAE J3061: Appendix F - VEHICLE LEVEL CONSIDERATIONS, Security Mechanisms, e. Central gateway or domain controller based architectures.
<<<

[REQUIREMENT]
UID: AGW-S-008
TITLE: Security Assurance
STATEMENT: These devices SHALL satisfy a comprehensive set of product security requirements to yield high assurance of correct operation in the face of adversarial inputs to the device.
CRITICALITY: High
PUB_REFS: >>>
SAE J3061: Appendix F - VEHICLE LEVEL CONSIDERATIONS, Security Mechanisms, b. Access control mechanisms to restrict access to critical ECUs, critical modes of every ECU (diagnostic mode), and their data.
SAE J3061: Appendix F - VEHICLE LEVEL CONSIDERATIONS, Security Mechanisms, c. Access control mechanisms that tend to restrict access to information about the operational state of the vehicle, privacy sensitive information, financially sensitive information, detailed design information, etc.
SAE J3061: Appendix F - VEHICLE LEVEL CONSIDERATIONS, Security Mechanisms, g. Mechanisms that effectively secure maintenance operations, including both diagnostic procedures and update procedures.
<<<

[REQUIREMENT]
UID: AGW-S-009
REFS:
- TYPE: Parent
  VALUE: AGW-S-007
TITLE: Preserves Performance
STATEMENT: The device SHALL be scoped to sufficient detail to preserve network domain performance guarantees in *TND*.
CRITICALITY: Medium

[REQUIREMENT]
UID: AGW-S-010
TITLE: Mode Switch Interlock
STATEMENT: >>>
The device SHALL have a means to temporarily disable the preventions listed previously and as noted with "unless with explicity authorized and authenticated configuration changes via the mode switch" The means must be impossible to use without explicit authorization by the vehicle owner. The device SHALL satisfy one or more of these methods to enable a switch into modes which allow OTA, spoofing, etc. from *UND* to *TND*. If more than one is satisfied then the effects of either switch could be in effect concurrently (i.e. a logical OR operation).

* Physical Mode Switch Interlock: The device SHALL have at least one physical input that when grounded enables a switch into modes which allow OTA, spoofing, etc. from *UND* to *TND*.

  * Example: Physical switch on dash

* Virtual Mode Switch Interlock: The device SHALL allow a explicitly authorized and authenticated input over a connection to enable a switch into modes which allow OTA, spoofing, etc. from *UND* to *TND*.

  * Example: Consent on Instrument cluster or infotainment device (and thus internal networks - possibly but not necessarily *TND*)

  * Example: Consent from third party device / application that is signed with infrastructure OEM has access to verify

<<<
TAGS: CONTAINS_OPTIONS
CRITICALITY: High
PUB_REFS: >>>
SAE J3061: Appendix F - VEHICLE LEVEL CONSIDERATIONS, Security Mechanisms, b. Access control mechanisms to restrict access to critical ECUs, critical modes of every ECU (diagnostic mode), and their data.
SAE J3061: Appendix F - VEHICLE LEVEL CONSIDERATIONS, Security Mechanisms, c. Access control mechanisms that tend to restrict access to information about the operational state of the vehicle, privacy sensitive information, financially sensitive information, detailed design information, etc.
SAE J3061: Appendix F - VEHICLE LEVEL CONSIDERATIONS, Security Mechanisms, g. Mechanisms that effectively secure maintenance operations, including both diagnostic procedures and update procedures.
<<<

[REQUIREMENT]
UID: AGW-S-011
TITLE: Mode Switch Indicated
STATEMENT: The device SHALL indicate to all domains that it is not performing normal operations.
CRITICALITY: Medium

[SECTION]
TITLE: Security Requirements for CAN Gateways

[FREETEXT]
The following security requirements must be satisfied by CAN gateways specifically. These CAN gateways are expected to meet all of the AGW-S-* Abstract Gateway security requirements and to also satisfy the CGW-S-* security requirements of this section.
[/FREETEXT]

[REQUIREMENT]
UID: CGW-S-001
REFS:
- TYPE: Parent
  VALUE: AGW-S-009
TITLE: Performant
STATEMENT: The device SHALL process and move CAN frames quickly enough to preserve performance on all network domains.
CRITICALITY: Medium

[SECTION]
TITLE: Preserves Atomic Multicast: CGW-S-005* Series

[FREETEXT]
The device SHALL preserve the atomic multicast property of CAN buses. All CGW-S-005* requirements must be satisfied.
[/FREETEXT]

[REQUIREMENT]
UID: CGW-S-005a
REFS:
- TYPE: Parent
  VALUE: AGW-S-007
TITLE: Won't Drop Frames
STATEMENT: The device SHALL NOT drop CAN frames in its bidirectional *UND* ↔ *TND* operation, unless with explicit configuration for rate limiting (AGW-F-006) or translation (AGW-F-002)
CRITICALITY: High

[REQUIREMENT]
UID: CGW-S-005b
REFS:
- TYPE: Parent
  VALUE: AGW-S-007
TITLE: No Priority Inversion
STATEMENT: The device SHALL schedule egress frames according to the CAN arbitration ID priority in it bidirectional *UND* ↔ *TND* operation, to prevent priority inversion.
CRITICALITY: High

[REQUIREMENT]
UID: CGW-S-005c
REFS:
- TYPE: Parent
  VALUE: AGW-S-007
TITLE: Preserves Ordering
STATEMENT: The device SHALL preserve ordering egress frames wrt their ingress order within an equivalence class of CAN arbitration ID priorities, to prevent out-of-order delivery.
CRITICALITY: High

[REQUIREMENT]
UID: CGW-S-005d
REFS:
- TYPE: Parent
  VALUE: AGW-S-007
TITLE: FIFO but Also Priority
STATEMENT: The device SHALL schedule egress for in-order send but not across CAN arbitration ID priorities.
CRITICALITY: High

[REQUIREMENT]
UID: CGW-S-005e
REFS:
- TYPE: Parent
  VALUE: AGW-S-007
TITLE: Preserves Jitter
STATEMENT: The device SHALL have ingress-to-egress latency variability (jitter) low enough to not affect the *TND* network domain performance requirements in the worst case.
CRITICALITY: Medium

[/SECTION]

[SECTION]
TITLE: Prevents CAN Attacks

[REQUIREMENT]
UID: CGW-S-006
REFS:
- TYPE: Parent
  VALUE: AGW-S-002
TITLE: Prevents Bus Flood Attacks
STATEMENT: The device SHALL prevent generating bus flood attacks on *TND* from messages originating on *UND*. c.f. https://canislabs.com/wp-content/uploads/2020/05/1901-2019-11-29-White-Paper-CAN-Security.pdf section 2.1 for a description of the bus flood attack.
CRITICALITY: High

[REQUIREMENT]
UID: CGW-S-007
REFS:
- TYPE: Parent
  VALUE: AGW-S-003
TITLE: Prevents (Simple) Frame Spoofing
STATEMENT: The device SHALL prevent generating simple frame spoofing attacks on *TND* from messages originating on *UND*. c.f. https://canislabs.com/wp-content/uploads/2020/05/1901-2019-11-29-White-Paper-CAN-Security.pdf section 2.2 for a description of simple frame spoofing attack.
CRITICALITY: High

[SECTION]
TITLE: Prevents CAN Protocol Attacks: CGW-S-008* Series

[FREETEXT]
The CAN gateways must prevent CAN protocol attacks in *TND*. At the time of drafting these requirements this can be accomplished by satisfying all of the CGW-S-008* requirements that follow.

CAN Protocol Attack
    Attacks on CAN networks requiring GPIO control of CAN_TX (and optionally CAN_RX) pins.

c.f. https://canislabs.com/wp-content/uploads/2020/05/1901-2019-11-29-White-Paper-CAN-Security.pdf section 2.1 for further definition of CAN protocol attacks.
[/FREETEXT]

[REQUIREMENT]
UID: CGW-S-008a
REFS:
- TYPE: Parent
  VALUE: AGW-S-003
TITLE: Prevents Adaptive Frame Spoofing
STATEMENT: The device SHALL prevent generating adaptive frame spoofing attacks on *TND* from messages originating on *UND*. c.f. https://canislabs.com/wp-content/uploads/2020/05/1901-2019-11-29-White-Paper-CAN-Security.pdf section 2.3 for a description of adaptive frame spoofing attack.
CRITICALITY: High

[REQUIREMENT]
UID: CGW-S-008b
REFS:
- TYPE: Parent
  VALUE: AGW-S-007
TITLE: Prevents Error Passive Attack Step
STATEMENT: The device SHALL prevent generating attacks that drive a ECU on *TND* into error passive state from messages originating on *UND*. This will in turn prevent error passive spoofing attacks c.f. https://canislabs.com/wp-content/uploads/2020/05/1901-2019-11-29-White-Paper-CAN-Security.pdf section 2.4 for a description of error passive spoofing attack.
CRITICALITY: High

[REQUIREMENT]
UID: CGW-S-008c
REFS:
- TYPE: Parent
  VALUE: AGW-S-007
TITLE: Prevents Double Receive Attack
STATEMENT: The device SHALL prevent generating double receive attacks on *TND* from messages originating on *UND*. c.f. https://canislabs.com/wp-content/uploads/2020/05/1901-2019-11-29-White-Paper-CAN-Security.pdf section 2.5 for a description of the double receive attack.
CRITICALITY: High

[REQUIREMENT]
UID: CGW-S-008d
REFS:
- TYPE: Parent
  VALUE: AGW-S-002
TITLE: Prevents Bus-Off Attack
STATEMENT: The device SHALL prevent generating bus-off attacks on *TND* from messages originating on *UND*. c.f. https://canislabs.com/wp-content/uploads/2020/05/1901-2019-11-29-White-Paper-CAN-Security.pdf section 2.6 for a description of the bus-off attack.
CRITICALITY: High

[REQUIREMENT]
UID: CGW-S-008e
REFS:
- TYPE: Parent
  VALUE: AGW-S-002
TITLE: Prevents Freeze Doom Loop Attack
STATEMENT: The device SHALL prevent generating freeze doom loop attacks on *TND* from messages originating on *UND*. c.f. https://canislabs.com/wp-content/uploads/2020/05/1901-2019-11-29-White-Paper-CAN-Security.pdf section 2.7 for a description of the freeze doom loop attack.
CRITICALITY: High

[/SECTION]

[REQUIREMENT]
UID: CGW-S-013
REFS:
- TYPE: Parent
  VALUE: AGW-S-008
TITLE: Impervious to Janus Attack
STATEMENT: The device SHALL not enable Janus Attacks in any group of OEM supplied components on any of its interface. c.f. https://kentindell.github.io/2021/07/15/janus-attack/ for a description of the Janus Attack.
COMMENT: Susceptibility to Janus Attacks is a property of a network of devices, not only of a single device. The entire *TND* is expected to be impervious to Janus Attacks since it should all be OEM supplied components there. In *UND* it is not possible to require that this device nor all the devices are impervious to Janus Attacks since *UND* is explicitly permitted to contain non-OEM supplied components. What is required of this device on *UND* is that if there are other OEM supplied devices on *UND* then this device cannot enable Janus Attacks on that collection of all those OEM supplied devices on *UND*.
CRITICALITY: Medium

[/SECTION]

[/SECTION]

[SECTION]
TITLE: Security Requirements for J1939 Gateways

[FREETEXT]
J1939 Gateways are expected to meet all of the CGW-S-* CAN Gateway Security Requirements and to also satisfy the J1939GW-S-* Security requirements of this section
[/FREETEXT]

[REQUIREMENT]
UID: J1939GW-S-039
REFS:
- TYPE: Parent
  VALUE: AGW-S-003
TITLE: Prevents J1939 Address Spoofing
STATEMENT: The device shall prevent the gatewaying (any of transport, translate, filter, or encapsulate) of any traffic onto *TND* with a J1939 address which is claimed by any of the devices in *TND*.
CRITICALITY: Medium

[REQUIREMENT]
UID: J1939GW-S-029
REFS:
- TYPE: Parent
  VALUE: AGW-S-002
TITLE: Prevents Address Claim Attacks
STATEMENT: The device SHALL prevent generating address claim attacks on *TND* from messages originating on *UND*. c.f. https://www.aut.upt.ro/~bgroza/Papers/j1939.pdf and https://doi.org/10.4271/02-14-03-0026 for a description of the address claim attack.
COMMENT: **Note to implementors**: Performing no gatewaying (any of transport, translate, filter, or encapsulate) of address claims onto *TND* would satisfy this requirement.
CRITICALITY: High

[REQUIREMENT]
UID: J1939GW-S-089
REFS:
- TYPE: Parent
  VALUE: AGW-S-008
TITLE: Impervious to Address Claim Attacks
STATEMENT: The device SHALL not be susceptible to address claim attacks on any of its interfaces (e.g. *TND* and *UND*)
CRITICALITY: High

[/SECTION]

[/SECTION]

[SECTION]
TITLE: Security Requirements for Abstract Unintended Gateways

[FREETEXT]
Security requirements that must be satisfied by any device which *could be* a gateway (due to malicious code) but is not intended to be one.
[/FREETEXT]

[REQUIREMENT]
UID: NGW-S-001
TITLE: Security Assurance
STATEMENT: These devices SHALL satisfy a comprehensive set of product security requirements to yield high assurance of correct operation in the face of adversarial inputs to the device.
CRITICALITY: High
PUB_REFS: >>>
SAE J3061: Appendix F - VEHICLE LEVEL CONSIDERATIONS, Security Mechanisms, b. Access control mechanisms to restrict access to critical ECUs, critical modes of every ECU (diagnostic mode), and their data.
SAE J3061: Appendix F - VEHICLE LEVEL CONSIDERATIONS, Security Mechanisms, c. Access control mechanisms that tend to restrict access to information about the operational state of the vehicle, privacy sensitive information, financially sensitive information, detailed design information, etc.
SAE J3061: Appendix F - VEHICLE LEVEL CONSIDERATIONS, Security Mechanisms, g. Mechanisms that effectively secure maintenance operations, including both diagnostic procedures and update procedures.
<<<

[SECTION]
TITLE: Prevents Gateway Functions

[REQUIREMENT]
UID: NGW-S-002
REFS:
- TYPE: Parent
  VALUE: NGW-S-001
TITLE: Won't Transport
STATEMENT: These devices SHALL NOT transport/'move' information between two separate network 'domains,' in either bidirection.
CRITICALITY: High


[REQUIREMENT]
UID: NGW-S-003
REFS:
- TYPE: Parent
  VALUE: NGW-S-001
TITLE: Won't Translate
STATEMENT: These devices SHALL NOT translate/transform the information between the separate network domains.
CRITICALITY: High

[REQUIREMENT]
UID: NGW-S-004
REFS:
- TYPE: Parent
  VALUE: NGW-S-001
TITLE: Won't Filter, Drop or Rate Limit
STATEMENT: These devices SHALL NOT select which information is transported and/or translated between the network domains.
CRITICALITY: High

[REQUIREMENT]
UID: NGW-S-005
REFS:
- TYPE: Parent
  VALUE: NGW-S-001
TITLE: Won't Encapsulate
STATEMENT: These devices SHALL NOT encapsulate information as it is transported and/or translated between the network domains.
CRITICALITY: High

[/SECTION]

[/SECTION]
