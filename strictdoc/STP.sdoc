[DOCUMENT]
TITLE: MIL-STD-498 STP (Software Test Plan)

[REQUIREMENT]
UID: STP-1
STATUS: Draft
TITLE: MIL-STD-498 STP (Software Test Plan)
STATEMENT: This requirement covers MIL-STD-498 STP (Software Test Plan).
RATIONALE: Converted from original document structure.

[REQUIREMENT]
UID: STP-2
STATUS: Draft
TITLE: Test Notes
STATEMENT: This requirement covers Test Notes.
RATIONALE: Converted from original document structure.
