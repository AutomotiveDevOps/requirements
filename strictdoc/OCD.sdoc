[DOCUMENT]
TITLE: MIL-STD-498 OCD (Operational Concept Document)

[REQUIREMENT]
UID: OCD-1
STATUS: Draft
TITLE: MIL-STD-498 OCD (Operational Concept Document)
STATEMENT: This requirement covers MIL-STD-498 OCD (Operational Concept Document).
RATIONALE: Converted from original document structure.

[REQUIREMENT]
UID: OCD-2
STATUS: Draft
TITLE: Operational Impact Assessment
STATEMENT: This requirement covers Operational Impact Assessment.
RATIONALE: Converted from original document structure.
