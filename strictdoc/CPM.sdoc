[DOCUMENT]
TITLE: MIL-STD-498 CPM (Computer Programming Manual)

[REQUIREMENT]
UID: CPM-1
STATUS: Draft
TITLE: MIL-STD-498 CPM (Computer Programming Manual)
STATEMENT: This requirement covers MIL-STD-498 CPM (Computer Programming Manual).
RATIONALE: Converted from original document structure.

[REQUIREMENT]
UID: CPM-2
STATUS: Draft
TITLE: Release Management
STATEMENT: This requirement covers Release Management.
RATIONALE: Converted from original document structure.
