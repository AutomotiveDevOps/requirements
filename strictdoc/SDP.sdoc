[DOCUMENT]
TITLE: MIL-STD-498 SDP (Software Development Plan)

[REQUIREMENT]
UID: SDP-1
STATUS: Draft
TITLE: MIL-STD-498 SDP (Software Development Plan)
STATEMENT: This requirement covers MIL-STD-498 SDP (Software Development Plan).
RATIONALE: Converted from original document structure.

[REQUIREMENT]
UID: SDP-2
STATUS: Draft
TITLE: Communication Plan
STATEMENT: This requirement covers Communication Plan.
RATIONALE: Converted from original document structure.
