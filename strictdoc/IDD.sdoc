[DOCUMENT]
TITLE: MIL-STD-498 IDD (Interface Design Description)

[REQUIREMENT]
UID: IDD-1
STATUS: Draft
TITLE: MIL-STD-498 IDD (Interface Design Description)
STATEMENT: This requirement covers MIL-STD-498 IDD (Interface Design Description).
RATIONALE: Converted from original document structure.

[REQUIREMENT]
UID: IDD-2
STATUS: Draft
TITLE: Security Interfaces
STATEMENT: This requirement covers Security Interfaces.
RATIONALE: Converted from original document structure.
