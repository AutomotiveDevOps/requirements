[DOCUMENT]
TITLE: MIL-STD-498 STR (Software Test Report)

[REQUIREMENT]
UID: STR-1
STATUS: Draft
TITLE: MIL-STD-498 STR (Software Test Report)
STATEMENT: This requirement covers MIL-STD-498 STR (Software Test Report).
RATIONALE: Converted from original document structure.

[REQUIREMENT]
UID: STR-2
STATUS: Draft
TITLE: Test Automation
STATEMENT: This requirement covers Test Automation.
RATIONALE: Converted from original document structure.
